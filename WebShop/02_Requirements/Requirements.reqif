# Specification: Specification Document
- Description: Requirements Document

## R1
The system shall be scalable for both hardware and software parts of the system

## R2
The system shall have an authentication mechanism.

## R3
The system shall have a role based authorization mechanism.

## R4
Every transaction and action shall be logged for tracing purposes.

## R5
The system shall provide a mechanism for logging errors and marking them by their severeness.
- links to -> R6

## R6
The system shall inform the system administrator via email or SMS in case of a highly severe error.
- links to -> R5

## R7
All system functionalities shall be implemented in a component based manner for increased maintainability

## R8
The application shall be internationalized (multilingual).

## R9
After application startup the administrator shall be presented with a login page.
- links to -> R10
- links to -> R11

## R10
If no administrator is present in the database, the administrator interface shall show a form for creating an admin account
- links to -> R9

## R11
In case the database is down the administrator shall be presented with an appropriate error message on application startup
- links to -> R9

## R12
On Application shutdown the application state shall be stored in the database, logout the application from the database and stop the application
- links to -> R13

## R13
On Application shutdown, customer shall be presented with an appropriate error message that the application will shutdown
- links to -> R12

## R14
The administrator shall be able to create and modify a default configuration over the server cli.

## R15
An administrator shall be able to create new administrator accounts as well as employee accounts and also edit and delete them

## R16
An employee account shall be able to create new customer accounts as well as edit and delete them.

## R17
A customer shall be able to create his own account as well as edit and delete it.
- links to -> R22

## R18
An admin should be able to create, edit and remove roles in the system.

## R19
Employees and customers shall be able to search products by keyword or product-code

## R20
Employees shall be able to place, edit and cancel orders.

## R21
Customers shall be able to place and cancel orders.

## R22
During account creation if a user already exists an error shall be shown in the browser with this information.
- links to -> R17
